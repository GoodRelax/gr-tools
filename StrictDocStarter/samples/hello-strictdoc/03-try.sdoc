[DOCUMENT]
TITLE: StrictDocStarter Sample - Hello StrictDoc
OPTIONS:
  MARKUP: Markdown

[TEXT]
STATEMENT: >>>
このファイルは StrictDocStarter 同梱のミニマルサンプル要求書です。

`manage-strictdoc.bat` をダブルクリック → `1` (Start) を選ぶと、
StrictDoc Web UI がブラウザで開き、 この内容が表示されます。

サンプル要求は計 3 件 (HELLO-001, HELLO-002, HELLO-003)。 後続の
`02-design.sdoc` で設計事項 (DESIGN-001, DESIGN-002) が参照します。
<<<

[REQUIREMENT]
UID: HELLO-X01
TITLE: Hello World メッセージ表示
STATEMENT: >>>
本システムは、 ユーザに対して "Hello, World" のメッセージを画面に表示すること。

![アーキテクチャ図](_assets/images/hage/hoge.png)
<<<

[REQUIREMENT]
UID: HELLO-X02
TITLE: UTF-8 日本語対応
STATEMENT: >>>
表示メッセージは UTF-8 でエンコードされた日本語文字列を含むことができること。
<<<
RELATIONS:
- TYPE: Parent
  VALUE: HELLO-X01

[REQUIREMENT]
UID: HELLO-X03
TITLE: 標準出力デバイスへの出力
STATEMENT: >>>
本システムは、 標準出力デバイス (コンソール、 ターミナル等) にメッセージを出力すること。
<<<
RELATIONS:
- TYPE: Parent
  VALUE: HELLO-X01
