[DOCUMENT]
TITLE: Appendix: Notation Reference
OPTIONS:
  MARKUP: Markdown

[TEXT]
STATEMENT: >>>
## A. About this appendix

This appendix consolidates the **StrictDoc notation** used in the SOVD requirements specification (00-11).
It is not about the requirements themselves; rather, it gathers in one place "how to write diagrams, equations, tables, images, and code so that
they render in StrictDoc," and at the same time doubles as a demo that **actually renders and shows the Markdown markup notation**.

Only this document declares `OPTIONS: MARKUP: Markdown` (00-11 use StrictDoc's default
**RST**). Because markup is determined **per document**, the RST notation (Mermaid via raw html,
`.. math::`, `.. image::`, `.. list-table::`) is actually used in the body of 00-11, while the
Markdown notation (fences, `![]()`, pipe tables) is demonstrated in this appendix.
<<<

[TEXT]
STATEMENT: >>>
## B. Choosing the markup (RST and Markdown)

| Notation | RST (used in 00-11) | Markdown (used in this appendix) |
|---|---|---|
| Headings | Section `[[SECTION]]` / RST headings | `##` headings |
| Mermaid diagram | `.. raw:: html` + `<pre class="mermaid">` (all versions) | ` ```mermaid ` fence (0.23.0+) |
| Equations | `.. math::` / `` :math:`...` `` | (MathJax is used on the RST side) |
| Images | `.. image:: path` | `![alt](path)` |
| Tables | `.. list-table::` | pipe table `\| ... \|` |
| Code | RST `.. code-block::` | ` ``` ` fence + language name |

**Note (version-dependent):** RST's raw-html Mermaid renders in all StrictDoc versions. Markdown's
` ```mermaid ` fence renders as a diagram only on **strictdoc 0.23.0 and later** and when the MERMAID feature is enabled
(before that it stops at a code block). The verified version for this sample is
**0.23.1**.
<<<

[TEXT]
STATEMENT: >>>
## C. Mermaid diagram (demonstration of the Markdown fence)

On the RST side (00-11) we use `.. raw:: html` + `<pre class="mermaid">`. In Markdown,
the following ` ```mermaid ` fence renders directly as a diagram.

```mermaid
flowchart LR
    Cloud["OEM Cloud /<br/>Workshop tool"] --> Net["Internet<br/>HTTPS"]
    Net --> TCU["TCU"]
    TCU --> GW["Gateway ECU"]
    GW --> ECU["In-vehicle ECUs<br/>(UDS)"]
```
<<<

[TEXT]
STATEMENT: >>>
## D. Equations (MathJax)

Equations are written in an RST `.. math::` block, or inline with `` :math:`...` ``
(in this sample they are used in the L2 of 03-auth for signature verification and the latency budget). Rendering requires the MATHJAX
feature. Example (RST notation):

```
.. math::

    t_{auth} = t_{verify} + t_{scope} \le 50\,\mathrm{ms}
```
<<<

[TEXT]
STATEMENT: >>>
## E. Images (demonstration of Markdown's `![]()`)

On the RST side (00-overview) an SVG is embedded with `.. image::`. In Markdown it is embedded with `![alt](path)`.
The following is the PNG version of the same architecture diagram (exported from the draw.io file in `_assets/`).

![SOVD remote diagnostics architecture diagram (PNG)](_assets/sovd-architecture.png)

The editing source for the diagram is `_assets/sovd-architecture.drawio`. From it, the SVG (for 00-overview) and
the PNG (for this appendix) are exported.
<<<

[TEXT]
STATEMENT: >>>
## F. Code highlighting (demonstration of fence + language name)

Code written in a fence with a language name is highlighted by Pygments (no feature needed, built in).
The following is a minimal example of a SOVD client (authentication -> DID read).

```python
import requests

# 1) Obtain access_token via OAuth2 PKCE (03-auth)
token = authorize(client_id, pkce_verifier)

# 2) Read a DID (rpm) with the Bearer token (04-data-access, TLS 1.3)
resp = requests.get(
    "https://vehicle.example/sovd/v1/components/engine/data/rpm",
    headers={"Authorization": f"Bearer {token}"},
    verify="oem_ca.pem",
)
print(resp.json())  # -> {"rpm": 824}
```
<<<

[TEXT]
STATEMENT: >>>
## G. Tables (demonstration of a Markdown pipe table)

On the RST side (00-overview) we use `.. list-table::`. In Markdown it is written as a pipe table.
Example: the main SOVD scopes.

| Scope | Permitted operation | Main document |
|---|---|---|
| `read:did` | Reading vehicle data (DIDs) | 04-data-access |
| `read:dtc` | Reading fault codes | 05-dtc-diagnostics |
| `write:dtc` | Clearing fault codes | 05-dtc-diagnostics |
| `write:swupdate` | OTA software update | 06-sw-update |
<<<
