[DOCUMENT]
TITLE: SOVD 車両診断システム 要求仕様 - 全体概要 (Overview / Foundation)

[GRAMMAR]
IMPORT_FROM_FILE: sovd-grammar.sgra

[TEXT]
STATEMENT: >>>
本書は StrictDocStarter 同梱の SOVD (Service-Oriented Vehicle Diagnostics) 要求仕様
サンプルの **全体概要 (Foundation)** である。 後続の要求文書
(03-auth / 04-data-access / 05-dtc-diagnostics / 06-sw-update) が共有する前付け —
目的・背景ストーリー・適用範囲・システム構成・用語・参照規格・表記規約・前提・
改訂履歴 — をここに集約する。

本サンプルは ANMS (AI-Native Minimal Spec) テンプレートの章構成 (Foundation →
Requirements → Architecture) を、 StrictDoc のカスタム文法と L0→L3 階層トレースに
適用した「自然な仕様書」の見本であり、 同時に StrictDoc の記法 (セクション・カスタム
フィールド・トレーサビリティ・図・数式・表) のデモを兼ねる。 記法そのものの書き方は
付録 `90-appendix-notation.sdoc` を参照のこと。 全文書は共通の要求フィールド定義
`sovd-grammar.sgra` を `IMPORT_FROM_FILE` で読み込む。
<<<

[[SECTION]]
TITLE: 1. 概要 (Background / Issues / Goals)

[TEXT]
STATEMENT: >>>
**1.1 背景 (Background) — なぜ SOVD なのか**

車が故障すると、 昔はドライバーが車をディーラーや整備工場へ持ち込むしかなかった。
整備士は車の診断コネクタ (OBD ポート) に専用の診断機を **有線で** つなぎ、
UDS (ISO 14229) という車載プロトコルで故障コード (DTC) や車両データを読み出して
原因を調べる。 この方式では **車が物理的にそこに無いと何もできず**、 専用機材と
人手も要る。 出先での故障対応、 多数の車両 (フリート) の一括把握、 不具合の早期発見が
難しい。

そこで、 **「車のところまで行って有線でつなぐ」のをやめ、 遠隔で診断したい**。
これを実現するのが本仕様の対象である。 車載の通信ユニット **TCU** (Telematics
Control Unit = 携帯回線でクラウドとつながる "車のモデム") と、 新しい診断方式
**SOVD** (診断を HTTP/REST の Web API として提供する仕組み) を組み合わせ、
インターネット越しに、 **認可された相手だけ** が車を遠隔診断・遠隔更新できるようにする。
<<<

[TEXT]
STATEMENT: >>>
**1.2 課題 (Issues) — 誰が何に困っているか**

.. list-table::
   :header-rows: 1
   :widths: 24 76

   * - ステークホルダ
     - 困りごと
   * - ドライバー / オーナー
     - 警告灯が点いても、 工場に着くまで原因が分からず不安。 工場へ行く回数を減らしたい。
   * - 整備士
     - 車が来てからでないと診断できない。 来ても毎回コネクタ接続の手間がかかる。
   * - OEM (メーカー)
     - 市場で起きている不具合を遠隔で把握し、 ソフト更新で直したい。
   * - フリート運用者
     - 何百台もの車両の健康状態を、 一台ずつ見に行けない。

加えて、 診断が **インターネット経由** になると「誰でも叩ける」 危険が生じる。
なりすまし・盗聴・改ざんを防ぐ **認証・認可・暗号** が、 全機能の共通の土台として
必須になる。
<<<

[TEXT]
STATEMENT: >>>
**1.3 目標 (Goals)**

本仕様は、 上記の遠隔診断を支える SOVD の 4 つの機能ドメインを定義する。

.. list-table::
   :header-rows: 1
   :widths: 30 70

   * - ドメイン (文書)
     - 遠隔で何ができるようになるか
   * - 認証・認可 (03-auth)
     - 正規の整備士 / OEM / フリートだけがアクセスでき、 権限で操作を分ける **土台**。
   * - データアクセス (04-data-access)
     - 走行距離・電圧・各 ECU 温度などの車両データを、 出先からでも読む。
   * - DTC 診断 (05-dtc-diagnostics)
     - 故障コードを遠隔で取得して原因の当たりをつけ、 修理後にクリアする。
   * - ソフト更新 / OTA (06-sw-update)
     - 工場に入れず、 不具合修正の新ファームを無線で配信する。

各ドメインは L0 (ステークホルダ) → L1 (システム) → L2 (ECU ソフトウェア) →
L3 (ユニット) の 4 層で分解し、 Parent/Child で連鎖させ、 機能安全 (ASIL) と
サイバーセキュリティ (CAL) の保証レベルを明示する。
<<<

[[/SECTION]]

[[SECTION]]
TITLE: 2. 適用範囲 (Scope)

[TEXT]
STATEMENT: >>>
**In-scope:**

- SOVD クライアント (クラウド / 整備ツール) ↔ 車両ゲートウェイ間の認証・認可 (03-auth)
- 車両データ識別子 (DID) / 周期データ / スナップショット / バルク転送の読み出し (04-data-access)
- 診断トラブルコード (DTC) ・フリーズフレームの読出・クリア (05-dtc-diagnostics)
- OTA ソフトウェア更新 (ダウンロード・署名検証・書込・ロールバック) (06-sw-update)
- 上記を L0 (ステークホルダ) → L1 (システム) → L2 (ECU ソフトウェア) → L3 (ユニット) で分解

**Out-of-scope:**

- TCU や OEM バックエンド (クラウド) 側の内部実装仕様 (本サンプルは車両側の要求が対象)
- 車載ネットワーク (CAN / Automotive Ethernet) の物理層・データリンク層
- 個別 ECU のアプリケーションロジック (診断対象そのものの機能)
- SOVD サーバ (車両側) の完全な実装仕様 (本サンプルは要求レベルまで)
- アクチュエータ駆動 (SOVD operations / ``exec:actuator`` スコープ) — 教材の焦点を
  認証・データ読出・DTC・OTA の 4 ドメインに絞るため、 本サンプルでは要求・API・テストを
  展開しない (SOVD 自体はアクチュエータ操作を備える)
<<<

[[/SECTION]]

[[SECTION]]
TITLE: 3. システム構成 (Architecture Overview)

[TEXT]
STATEMENT: >>>
**3.1 システム構成と仕組み**

遠隔診断の経路は次のとおり。 クラウドや整備ツール (SOVD クライアント) が
インターネット経由で車両につながり、 車載の TCU が携帯回線でその通信を中継する。
車内ではゲートウェイ ECU が SOVD (HTTP) を終端し、 従来どおり UDS で各 ECU へ
橋渡しする。

.. raw:: html

    <pre class="mermaid">
    flowchart LR
        Cloud["OEM クラウド /<br/>整備ツール<br/>(SOVD クライアント)"]
        Net["インターネット<br/>HTTPS / TLS 1.3"]
        TCU["TCU<br/>(車載通信ユニット /<br/>携帯回線)"]
        GW["ゲートウェイ ECU<br/>SOVD 終端 +<br/>SOVD↔UDS 変換"]
        E1["Engine ECU"]
        E2["Brake ECU"]
        E3["Body ECU"]
        Cloud --> Net --> TCU --> GW
        GW -->|UDS / 車載NW| E1
        GW -->|UDS / 車載NW| E2
        GW -->|UDS / 車載NW| E3
    </pre>

下図は draw.io で描いた詳細な構成図 (SVG 埋め込みのデモを兼ねる)。

.. image:: _assets/sovd-architecture.svg
   :alt: SOVD remote diagnostics architecture (cloud - internet - TCU - gateway ECU - in-vehicle ECUs)
   :width: 760px
<<<

[TEXT]
STATEMENT: >>>
**3.2 要求レイヤモデル (L0 → L3)**

本仕様の全要求は、 A-SPICE / V 字に倣った 4 層で分解され、 上位から下位へ
Parent/Child で連鎖する。 各機能ドメイン (03〜06) はこの 4 層を縦に貫く。 さらに、
機能をまたいで再利用される L3 ユニットは `07-common-platform` に集約し、 各機能の
L2 要求がそこへ収束 (N→1) する (分解の逆向き＝共有・再利用)。

.. raw:: html

    <pre class="mermaid">
    graph TD
        L0["L0 Stakeholder<br/>ステークホルダ要求<br/>(整備士 / OEM の目的)"]
        L1["L1 System<br/>システム要求<br/>(SOVD API / 車両)"]
        L2["L2 ECU Software<br/>ECU ソフトウェア要求<br/>(ゲートウェイ ECU)"]
        L3["L3 Unit<br/>ユニット要求<br/>(ソフトウェアコンポーネント)"]
        L0 --> L1 --> L2 --> L3
    </pre>
<<<

[TEXT]
STATEMENT: >>>
**3.3 SOVD リソースと機能ドメインのマッピング**

SOVD は機能を HTTP リソース (method + path) として公開する。 各リソースには
必要スコープ (03-auth で定義) が紐づく。

.. list-table::
   :header-rows: 1
   :widths: 12 40 28 20

   * - Method
     - SOVD リソース (例)
     - 機能ドメイン (文書)
     - 必要スコープ
   * - GET
     - ``/components/{ecu}/data/{did}``
     - Data Access (04)
     - ``read:did``
   * - GET
     - ``/components/{ecu}/faults``
     - DTC / Diagnostics (05)
     - ``read:dtc``
   * - DELETE
     - ``/components/{ecu}/faults``
     - DTC / Diagnostics (05)
     - ``write:dtc``
   * - POST
     - ``/updates``
     - SW Update / OTA (06)
     - ``write:swupdate``

※ 本表は SOVD リソースの代表例であり、 HTTP API の正式な契約は `09-api.sdoc` を
参照のこと (本サンプルは教材のため、 API 契約には主要リソースを抜粋している。 全 DTC
一括クリアなど、 本表の一部は契約への掲載を割愛している)。
<<<

[TEXT]
STATEMENT: >>>
**3.4 文書構成**

.. list-table::
   :header-rows: 1
   :widths: 30 50 20

   * - 文書
     - 内容
     - 層
   * - 00-overview (本書)
     - 目的・背景ストーリー・範囲・用語・参照規格・表記規約・改訂履歴
     - 前付け
   * - 01-stakeholder-requirements
     - ステークホルダ要求 (最上位 SYS-L0-001 + 各ドメイン L0、 EARS)
     - L0 要求
   * - 02-usecases
     - ユースケース (アクター・UC 図・UC-000〜004 のシナリオ)
     - L0 UC
   * - 03-auth
     - 認証・認可 (OAuth2 / JWT / TLS / RBAC)
     - L1–L3
   * - 04-data-access
     - 車両データ識別 (DID) / 読み出し
     - L1–L3
   * - 05-dtc-diagnostics
     - DTC / フリーズフレーム
     - L1–L3
   * - 06-sw-update
     - OTA 更新 / 署名検証 / ロールバック
     - L1–L3
   * - 07-common-platform
     - 共通基盤: 複数機能が再利用する共有ユニット (UDS転送 / 認可 / TLS / JSON)
     - L3 (共有)
   * - 08-architecture
     - システムアーキテクチャ: 方式 / コンポーネント / モジュール / クラス / 振る舞い / ADR
     - 設計 (HOW)
   * - 09-api
     - SOVD HTTP API 契約 (連携相手向け)
     - 契約
   * - 10-test-spec
     - テスト仕様 (戦略 + 単体 / 結合 / システム / 受入)
     - テスト (仕様)
   * - 11-test-results
     - テスト結果 (実行記録、 仕様と分離。 1 仕様 : N 結果)
     - テスト (結果)
   * - 90-appendix-notation
     - 表記・記法リファレンス (RST / Markdown / Mermaid / 数式 / 表 / コード)
     - 付録

本サンプルは「**ステークホルダ要求 (01) / ユースケース (02) → 要求 (03-07) → 設計 (08) →
API 契約 (09) → テスト仕様 (10) → 結果 (11)**」の V 字を、 ``Implements`` /
``Satisfies`` / ``Verifies`` / ``ResultOf`` 関係で一気通貫にトレースする (DEEP TRACE で
要求のテスト被覆と未達まで追える)。 ユースケース (02-usecases) は要求 (01) を実現し、
受入テスト (AT) が UC を検証する (IEEE 29148 流に要求と UC を分離)。

※ 全 .sdoc が共有する要求フィールド定義は `sovd-grammar.sgra` (StrictDoc の
grammar ファイル) に置き、 各文書が `IMPORT_FROM_FILE` で読み込む。
<<<

[[/SECTION]]

[[SECTION]]
TITLE: 4. 用語集 (Glossary)

[TEXT]
STATEMENT: >>>
.. list-table::
   :header-rows: 1
   :widths: 22 78

   * - 用語
     - 説明
   * - SOVD
     - Service-Oriented Vehicle Diagnostics。 HTTP/REST ベースの車両診断方式 (ASAM SOVD / ISO 17978)。
   * - UDS
     - Unified Diagnostic Services (ISO 14229)。 従来の車載診断プロトコル。 ゲートウェイが SOVD から UDS へ変換する。
   * - OBD ポート
     - 車両の診断コネクタ。 従来は診断機を有線で接続する物理 IF。
   * - TCU
     - Telematics Control Unit。 携帯回線でクラウドとつながる車載通信ユニット ("車のモデム")。 遠隔診断の通信を中継する。
   * - ECU
     - Electronic Control Unit。 車載の電子制御ユニット。
   * - Gateway ECU
     - 車外 IF (SOVD/HTTP) を終端し、 内部 ECU へ UDS を中継する車載ゲートウェイ。
   * - DID
     - Data Identifier。 車両データ項目を識別する 16-bit 番号 (例: 0xF40C = エンジン回転数)。
   * - DTC
     - Diagnostic Trouble Code。 故障コード。 車が「どこが悪いか」を記録したもの。
   * - Freeze Frame
     - DTC 発生時点の車両状態スナップショット。
   * - OTA
     - Over-The-Air。 無線によるソフトウェア更新。
   * - OAuth 2.0 / PKCE
     - 認可フレームワーク (RFC 6749) と公開クライアント向けの保護拡張 (PKCE、 RFC 7636)。
   * - JWT
     - JSON Web Token (RFC 7519)。 署名付きアクセストークン形式。
   * - mTLS
     - 相互 TLS。 サーバとクライアントの双方が X.509 証明書で認証する方式。
   * - スコープ
     - トークンが許可する操作範囲 (例: ``read:did`` / ``write:dtc`` / ``write:swupdate``)。
   * - ASIL
     - Automotive Safety Integrity Level (ISO 26262)。 機能安全の保証レベル (QM < A < B < C < D)。
   * - CAL
     - Cybersecurity Assurance Level (ISO/SAE 21434)。 サイバーセキュリティの保証レベル (CAL1 < … < CAL4)。
   * - NRC
     - Negative Response Code。 UDS の否定応答コード。
   * - A/B パーティション
     - 更新用に 2 系統のファームウェア領域を持ち、 切替で更新・ロールバックする方式。
<<<

[[/SECTION]]

[[SECTION]]
TITLE: 5. 参照規格 (Referenced Standards)

[TEXT]
STATEMENT: >>>
- **ASAM SOVD v1.0** — Service-Oriented Vehicle Diagnostics (Part 1: Common, Part 2: Data Model)
- **ISO 17978** — SOVD の国際標準化
- **ISO 14229-1** — UDS (Unified Diagnostic Services)
- **ISO 26262** — 自動車 機能安全 (ASIL)
- **ISO/SAE 21434** — 自動車 サイバーセキュリティエンジニアリング (CAL)
- **RFC 6749 / RFC 7636** — OAuth 2.0 / PKCE
- **RFC 7519** — JSON Web Token (JWT)
- **RFC 8446** — TLS 1.3
- **RFC 8259** — JSON データ交換形式
- **RFC 2119 / RFC 8174** — 要求レベルキーワード (MUST / SHALL / SHOULD / MAY)
- **MISRA C:2012** — 車載 C 言語コーディング規約 (L3 ユニットの実装制約)
<<<

[[/SECTION]]

[[SECTION]]
TITLE: 6. 表記規約 (Notation)

[TEXT]
STATEMENT: >>>
**6.1 要求レベルキーワード (RFC 2119 / 8174)**

「すること」 (= SHALL / MUST) は必須、 「推奨」 (= SHOULD) は推奨、
「してもよい」 (= MAY) は任意を表す。 EARS の ``shall`` は SHALL と同義。
<<<

[TEXT]
STATEMENT: >>>
**6.2 EARS 構文 (要求文の書式)**

全要求文は EARS (Easy Approach to Requirements Syntax) に従い、 主語を明示した
能動態・単一要求・検証可能な形で記述する。 日本語キーワードとの対応は次のとおり。

.. list-table::
   :header-rows: 1
   :widths: 22 33 45

   * - パターン
     - 日本語の形
     - 用途
   * - Ubiquitous
     - 「<主語> は <応答> すること。」
     - 常に成り立つ要求
   * - Event-driven
     - 「<トリガ> したとき、 <主語> は <応答> すること。」
     - イベント起点の要求
   * - State-driven
     - 「<状態> の間、 <主語> は <応答> すること。」
     - 状態依存の要求
   * - Unwanted
     - 「もし <トリガ> した場合、 <主語> は <応答> すること。」
     - 異常系・禁止事項
   * - Optional
     - 「<機能> を備える構成では、 <主語> は <応答> すること。」
     - オプション機能
   * - Complex
     - 上記の組合せ
     - 複合条件

主語は層ごとに具体化する: L0 = 本システム、 L1 = 車両 (SOVD ゲートウェイ)、
L2 = ゲートウェイ ECU、 L3 = 各ソフトウェアユニット。
<<<

[TEXT]
STATEMENT: >>>
**6.3 保証レベル: ASIL と CAL の使い分け (重要)**

本仕様では **安全** と **セキュリティ** を別の規格で分類し、 取り違えない。

- **ASIL** (ISO 26262、 機能安全): E/E システムの誤動作が **人身傷害につながるハザード**
  を生むかで決まる (QM / A / B / C / D)。 安全関連でない要求は **QM**。
- **CAL** (ISO/SAE 21434、 サイバーセキュリティ): 攻撃の実現可能性と影響に基づく
  セキュリティ保証レベル (CAL1〜CAL4)。

したがって認証・暗号・トークン等の **純粋なセキュリティ要求は ASIL=QM** とし、
代わりに **CAL** で保証レベルを表す。 一方、 走行中フラッシュ禁止や安全関連 DTC の
ように **誤動作が直接ハザードに至る要求は ASIL (B〜D)** を付与する。 両者が関わる
要求 (例: 改ざんされた FW の適用阻止) は ASIL と CAL の両方を持つ。
<<<

[TEXT]
STATEMENT: >>>
**6.4 要求フィールド (カスタム文法)**

各 [REQUIREMENT] は次のフィールドを持つ。 定義は共有ファイル `sovd-grammar.sgra`
にあり、 各文書が `[GRAMMAR] / IMPORT_FROM_FILE` で読み込む。

.. list-table::
   :header-rows: 1
   :widths: 20 80

   * - フィールド
     - 意味
   * - UID
     - 一意識別子。 ``<ドメイン>-<層>-<連番>`` (例: ``AUTH-L1-001``)。
   * - TYPE
     - Functional / Non-Functional / Constraint / Restriction / UseCase
   * - ASIL
     - 機能安全保証レベル (QM / A / B / C / D)
   * - CAL
     - サイバーセキュリティ保証レベル (CAL1–CAL4、 セキュリティ関連要求のみ)
   * - LAYER
     - L0_Stakeholder / L1_System / L2_ECU_SW / L3_Unit
   * - STATEMENT
     - EARS 形式の要求文
   * - RATIONALE
     - 根拠 (なぜこの要求が必要か。 任意)
   * - VERIFICATION
     - 受入基準 (どう検証すれば満たしたと言えるか。 任意)
   * - RELATIONS
     - Parent / Child による上位・下位要求へのトレース
<<<

[[/SECTION]]

[[SECTION]]
TITLE: 7. 前提・制約 (Assumptions & Constraints)

[TEXT]
STATEMENT: >>>
- 車両は TCU により携帯回線でクラウドへ接続でき、 遠隔から SOVD (HTTP/TLS) で
  到達できる構成を前提とする。 近接接続 (整備工場の LAN 等) も同じ SOVD API で扱える。
- ゲートウェイ ECU が SOVD を終端し、 内部は UDS にブリッジする。
- 信頼境界は車両ゲートウェイの外部 IF に置く。 車載ネットワーク内部は別の安全機構で保護される前提。
- 本サンプルは教材であり、 数値 (レイテンシ・容量等) は代表的な目安であって特定車両の実値ではない。
- L3 ユニットの実装言語は MISRA C:2012 準拠の C を前提とする (安全・セキュリティ関連)。
<<<

[[/SECTION]]

[[SECTION]]
TITLE: 8. 改訂履歴 (Revision History)

[TEXT]
STATEMENT: >>>
.. list-table::
   :header-rows: 1
   :widths: 14 18 68

   * - 版
     - 日付
     - 変更内容
   * - v0.1
     - 2026-06-06
     - 初版。 ANMS テンプレート準拠へ全面リライト。 遠隔診断の背景ストーリーを起点に
       前付け (本書) を新設し、 要求文を EARS 化、 ASIL/CAL を分離、 受入基準
       (VERIFICATION) とトレースを整備。 文法を `sovd-grammar.sgra` に共通化。
       旧 05/06 記法デモは本文へ統合し、 付録 90 に再編。
<<<

[[/SECTION]]
