[DOCUMENT]
TITLE: SOVD 記法デモ - Markdown (表 / コード / 画像 / Mermaid フェンス)
OPTIONS:
  MARKUP: Markdown

[GRAMMAR]
ELEMENTS:
- TAG: REQUIREMENT
  FIELDS:
  - TITLE: UID
    TYPE: String
    REQUIRED: True
  - TITLE: TYPE
    TYPE: SingleChoice(Functional, Non-Functional, Constraint, Restriction, UseCase)
    REQUIRED: True
  - TITLE: ASIL
    TYPE: SingleChoice(QM, A, B, C, D)
    REQUIRED: True
  - TITLE: LAYER
    TYPE: SingleChoice(L0_Stakeholder, L1_System, L2_ECU_SW, L3_Unit)
    REQUIRED: True
  - TITLE: TITLE
    TYPE: String
    REQUIRED: True
  - TITLE: STATEMENT
    TYPE: String
    REQUIRED: True
  - TITLE: RATIONALE
    TYPE: String
    REQUIRED: False
  RELATIONS:
  - TYPE: Parent
  - TYPE: Child

[TEXT]
STATEMENT: >>>
このドキュメントは **Markdown マークアップ** (`OPTIONS: MARKUP: Markdown`) での記法デモです。
SOVD (ASAM SOVD / ISO 17978) を題材に、 表・箇条書き・コードハイライト・画像・
そして **Mermaid フェンス** ( ```mermaid ) を 1 ファイルで示します。

Mermaid フェンス ( ```mermaid ) は strictdoc 0.23.0 以降 + MERMAID 有効時に図として
描画されます (0.22 以前ではコードブロック止まり)。 RST の raw html 版デモは
05-notation-rst.sdoc を参照してください。
<<<

[TEXT]
STATEMENT: >>>
## (1) SOVD リソースと機能ドメインのマッピング (表)

| HTTP method | SOVD リソース (例) | 機能ドメイン | 必要スコープ |
|---|---|---|---|
| GET  | `/components/{ecu}/data/{did}`       | Data Access      | `read:did`      |
| GET  | `/components/{ecu}/faults`           | DTC / Diagnostics | `read:dtc`      |
| POST | `/components/{ecu}/operations/{op}`  | Actuator         | `exec:actuator` |
| POST | `/updates`                           | SW Update (OTA)  | `write:swupdate`|

主な SOVD ケイパビリティ:

- **Data Access** — DID / リソースの読み出し (`read:did`)
- **DTC / Diagnostics** — 故障コードとフリーズフレームの取得 (`read:dtc`)
- **Actuator** — アクチュエータ駆動などの操作 (`exec:actuator`)
- **SW Update (OTA)** — 署名付きパッケージの配信と適用 (`write:swupdate`)
<<<

[REQUIREMENT]
UID: NOTE-MD-001
TYPE: Functional
ASIL: B
LAYER: L1_System
TITLE: SOVD リソースの HTTP マッピング
STATEMENT: >>>
車両は上表のとおり、 各機能ドメインを SOVD の HTTP リソース (method + path) に
マッピングし、 リソースごとに必要スコープを定義すること。
<<<
RELATIONS:
- TYPE: Parent
  VALUE: DATA-L1-001

[TEXT]
STATEMENT: >>>
## (2) SOVD クライアントの最小例 (コードハイライト)

```python
import requests

# 1) OAuth2 PKCE で access_token を取得
token = authorize(client_id, pkce_verifier)

# 2) Bearer トークンで DID (rpm) を読み出し (TLS 1.3)
resp = requests.get(
    "https://vehicle.local/sovd/v1/components/engine/data/rpm",
    headers={"Authorization": f"Bearer {token}"},
    verify="oem_ca.pem",
)
print(resp.json())  # -> {"rpm": 824}
```
<<<

[TEXT]
STATEMENT: >>>
## (3) システム構成図 (drawio から書き出した PNG)

![SOVD システム構成図](_assets/sovd-architecture.png)

同じ図の SVG 版は 05-notation-rst.sdoc で使用しています。
<<<

[TEXT]
STATEMENT: >>>
## (4) OTA 更新のステートマシン (Mermaid フェンス)

```mermaid
stateDiagram-v2
    [*] --> Idle
    Idle --> Downloading: POST /updates
    Downloading --> Verifying: package received
    Verifying --> Installing: signature valid
    Verifying --> Failed: signature invalid
    Installing --> Activated: flash OK
    Installing --> RolledBack: flash error
    Activated --> [*]
    RolledBack --> Idle
    Failed --> Idle
```
<<<

[REQUIREMENT]
UID: NOTE-MD-002
TYPE: Functional
ASIL: B
LAYER: L1_System
TITLE: OTA 更新ステートマシンの遵守
STATEMENT: >>>
OTA 更新は上図のステートマシンに従うこと。 署名検証 (Verifying) に失敗した場合は
Installing に遷移せず Failed とし、 フラッシュ失敗時は RolledBack で旧版に戻すこと。
<<<
RATIONALE: >>>
署名検証失敗パッケージの適用を状態遷移で構造的に禁止する。
<<<
RELATIONS:
- TYPE: Parent
  VALUE: SWU-L1-001
