[DOCUMENT]
TITLE: SOVD 車両データアクセス 要求仕様 (Vehicle Data Access)

[GRAMMAR]
IMPORT_FROM_FILE: sovd-grammar.sgra

[TEXT]
STATEMENT: >>>
本書は SOVD の **車両データアクセス** (DID 読み出し・周期データ・スナップショット・
バルク転送) の要求を L1→L3 で定義する。 ステークホルダ要求 (L0)・ユースケースは
`01-stakeholder-requirements.sdoc`、 共有の前付け (背景ストーリー・用語・表記規約・
ASIL/CAL の使い分け) は `00-overview.sdoc` を参照。 認証・認可は `02-auth.sdoc` を前提とする。

データ読み出しは安全機能ではないため原則 **ASIL=QM**。 ただし「誰がどのデータを読めるか」
の **アクセス制御はセキュリティ事項** なので、 該当要求には **CAL** を付与する。
<<<

[[SECTION]]
TITLE: L1 — システム要求 (System Requirements)

[TEXT]
STATEMENT: >>>
**L1 代表シーケンス: DID 読み出しの SOVD↔UDS 変換**

クライアントの SOVD (HTTP) 要求を、 ゲートウェイがスコープ検証のうえ UDS
ReadDataByIdentifier に変換し、 結果を JSON で返す。

.. raw:: html

    <pre class="mermaid">
    sequenceDiagram
        participant C as SOVD Client
        participant G as Gateway ECU
        participant E as Engine ECU
        C->>G: GET /components/engine/data/rpm (Bearer JWT)
        G->>G: verify scope read:did / resolve DID 0xF40C
        G->>E: UDS ReadDataByIdentifier (0x22 F40C)
        E-->>G: 0x62 F40C 0338
        G-->>C: 200 OK {"rpm": 824}
    </pre>
<<<

[REQUIREMENT]
UID: DATA-L1-001
TYPE: Functional
ASIL: QM
LAYER: L1_System
TITLE: DID ベースのデータ識別
STATEMENT: >>>
車両は、 全車両データを 16-bit DID (Data Identifier) で識別し、 SOVD API
(GET /components/{ecu}/data/{did}) で取得できるようにすること。
<<<
RELATIONS:
- TYPE: Parent
  VALUE: DATA-L0-001

[REQUIREMENT]
UID: DATA-L1-002
TYPE: Functional
ASIL: QM
LAYER: L1_System
TITLE: 周期データストリーム
STATEMENT: >>>
クライアントが複数 DID を購読したとき、 車両は Server-Sent Events または WebSocket で
周期的にプッシュ配信すること。
<<<
RELATIONS:
- TYPE: Parent
  VALUE: DATA-L0-002

[REQUIREMENT]
UID: DATA-L1-003
TYPE: Functional
ASIL: QM
LAYER: L1_System
TITLE: バルクダウンロード API
STATEMENT: >>>
車両は、 HTTP Range ヘッダによるレジューム可能なバルクダウンロード API を
提供すること。
<<<
RELATIONS:
- TYPE: Parent
  VALUE: DATA-L0-004

[REQUIREMENT]
UID: DATA-L1-004
TYPE: Constraint
ASIL: QM
LAYER: L1_System
TITLE: JSON ペイロード形式
STATEMENT: >>>
車両が返す DID 値の応答は、 JSON 形式とし、 スキーマは ASAM SOVD 仕様 Part 2
(Data Model) に準拠すること。
<<<
RELATIONS:
- TYPE: Parent
  VALUE: DATA-L0-001

[REQUIREMENT]
UID: DATA-L1-005
TYPE: Non-Functional
ASIL: QM
LAYER: L1_System
TITLE: 読み出しレイテンシ
STATEMENT: >>>
車両の単一 DID 読み出しの応答時間は、 95 パーセンタイルで 500 ms 以内であること。
<<<
VERIFICATION: >>>
代表負荷下で、 単一 DID の GET 応答の p95 が 500 ms 以内であること。
<<<
RELATIONS:
- TYPE: Parent
  VALUE: DATA-L1-001

[REQUIREMENT]
UID: DATA-L1-006
TYPE: Functional
ASIL: QM
CAL: CAL3
LAYER: L1_System
TITLE: スコープによるデータマスキング
STATEMENT: >>>
もし個人情報を含む DID (オーナー氏名等) へ Mechanic ロールがアクセスした場合、
車両は HTTP 403 を返すこと (OEMEngineer ロールのみアクセス可)。
<<<
RATIONALE: >>>
個人情報の保護。 役割に応じた最小権限を徹底する。
<<<
RELATIONS:
- TYPE: Parent
  VALUE: DATA-L0-005

[REQUIREMENT]
UID: DATA-L1-007
TYPE: Constraint
ASIL: QM
LAYER: L1_System
TITLE: ASAM SOVD データモデル準拠
STATEMENT: >>>
車両のデータアクセス API は、 ASAM SOVD v1.0 Part 2 のデータ識別子モデルに
準拠すること。
<<<

[[/SECTION]]

[[SECTION]]
TITLE: L2 — ECU ソフトウェア要求 (ECU Software Requirements)

[REQUIREMENT]
UID: DATA-L2-001
TYPE: Functional
ASIL: QM
LAYER: L2_ECU_SW
TITLE: DID リゾルバ
STATEMENT: >>>
ゲートウェイ ECU は、 DID から物理 ECU (CAN node) へのマッピングテーブルを保持し、
受信した DID を担当 ECU へルーティングすること。
<<<
RELATIONS:
- TYPE: Parent
  VALUE: DATA-L1-001

[REQUIREMENT]
UID: DATA-L2-002
TYPE: Functional
ASIL: QM
LAYER: L2_ECU_SW
TITLE: UDS ReadDataByIdentifier ブリッジ
STATEMENT: >>>
SOVD GET 要求を受信したとき、 ゲートウェイ ECU は担当 ECU へ UDS
ReadDataByIdentifier (0x22) を送信し、 応答を JSON に変換して返すこと。
<<<
RELATIONS:
- TYPE: Parent
  VALUE: DATA-L1-001

[REQUIREMENT]
UID: DATA-L2-003
TYPE: Non-Functional
ASIL: QM
LAYER: L2_ECU_SW
TITLE: 周期データキャッシュ
STATEMENT: >>>
ゲートウェイ ECU は、 頻繁にアクセスされる DID 値を 100 ms TTL の LRU キャッシュに
保持し、 ECU 通信回数を削減すること。
<<<
RELATIONS:
- TYPE: Parent
  VALUE: DATA-L1-005

[REQUIREMENT]
UID: DATA-L2-004
TYPE: Functional
ASIL: QM
LAYER: L2_ECU_SW
TITLE: WebSocket サブスクリプション
STATEMENT: >>>
ゲートウェイ ECU は WebSocket エンドポイントを提供し、 クライアント当たり最大
32 DID の同時購読を許容すること。
<<<
RELATIONS:
- TYPE: Parent
  VALUE: DATA-L1-002

[REQUIREMENT]
UID: DATA-L2-005
TYPE: Functional
ASIL: QM
LAYER: L2_ECU_SW
TITLE: バルクデータ圧縮
STATEMENT: >>>
バルクダウンロード時、 ゲートウェイ ECU は Content-Encoding: gzip による圧縮転送を
サポートすること。
<<<
RELATIONS:
- TYPE: Parent
  VALUE: DATA-L1-003

[REQUIREMENT]
UID: DATA-L2-006
TYPE: Functional
ASIL: QM
CAL: CAL3
LAYER: L2_ECU_SW
TITLE: スコープ評価ミドルウェア
STATEMENT: >>>
ゲートウェイ ECU は、 各 DID にアクセス可能スコープのメタデータを付随させ、
リクエスト処理時に ScopeAuthorizer (PLAT-L3-002) でチェックすること。
<<<
RELATIONS:
- TYPE: Parent
  VALUE: DATA-L1-006

[REQUIREMENT]
UID: DATA-L2-007
TYPE: Non-Functional
ASIL: QM
LAYER: L2_ECU_SW
TITLE: メモリ使用上限
STATEMENT: >>>
ゲートウェイ ECU のデータアクセス機能全体のヒープ使用量は、 4 MB 以内とすること。
<<<
RELATIONS:
- TYPE: Parent
  VALUE: DATA-L2-002

[REQUIREMENT]
UID: DATA-L2-008
TYPE: Constraint
ASIL: QM
LAYER: L2_ECU_SW
TITLE: ノンブロッキング I/O スレッドモデル
STATEMENT: >>>
ゲートウェイ ECU のデータ取得はノンブロッキング I/O (epoll 系) で実装し、 同時
100 接続をシングルスレッドで処理可能とすること。
<<<
RELATIONS:
- TYPE: Parent
  VALUE: DATA-L1-005

[[/SECTION]]

[[SECTION]]
TITLE: L3 — ユニット要求 (Unit / Software Component Requirements)

[REQUIREMENT]
UID: DATA-L3-001
TYPE: Functional
ASIL: QM
LAYER: L3_Unit
TITLE: DidResolver ユニット
STATEMENT: >>>
DidResolver ユニットは、 (did_number) → (ecu_address, parameter_layout) の
マッピング検索を O(1) のハッシュテーブルで行うこと。
<<<
RELATIONS:
- TYPE: Parent
  VALUE: DATA-L2-001

[REQUIREMENT]
UID: DATA-L3-002
TYPE: Functional
ASIL: QM
LAYER: L3_Unit
TITLE: DataCache ユニット
STATEMENT: >>>
DataCache ユニットは、 LRU + TTL ベースのキャッシュを提供し、 容量・TTL を
コンストラクタ引数で設定可能とすること。
<<<
RELATIONS:
- TYPE: Parent
  VALUE: DATA-L2-003

[REQUIREMENT]
UID: DATA-L3-003
TYPE: Constraint
ASIL: QM
LAYER: L3_Unit
TITLE: 浮動小数点の表現
STATEMENT: >>>
JsonSerializer の浮動小数点出力は IEEE 754 double とし、 NaN / Infinity は null として
表現すること (RFC 8259 準拠)。
<<<
RELATIONS:
- TYPE: Parent
  VALUE: PLAT-L3-004

[[/SECTION]]
