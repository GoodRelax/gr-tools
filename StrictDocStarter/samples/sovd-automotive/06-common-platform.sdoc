[DOCUMENT]
TITLE: SOVD 共通プラットフォーム 要求仕様 (Common Platform / Shared Components)

[GRAMMAR]
IMPORT_FROM_FILE: sovd-grammar.sgra

[TEXT]
STATEMENT: >>>
本書は、 複数の機能ドメイン (02-auth / 03-data-access / 04-dtc-diagnostics /
05-sw-update) が **共通で再利用する** ゲートウェイ基盤のユニット要求を集約する。
各機能ドメインの要求 (L2_ECU_SW) は、 ここに定義する基盤ユニットへ収束 (N→1) する。

**依存方向:** 機能 → 基盤 の一方向。 これにより「ある機能が別の機能 (兄弟) の文書に
依存する」 不健全な結合を避け、 共有部品の責務と所在を一箇所に固定する
(Clean Architecture の依存方向・SoC/SRP、 A-SPICE のプラットフォーム要素管理に対応)。

共有の前付け (用語・表記規約・ASIL/CAL の使い分け) は `00-overview.sdoc` を参照。
<<<

[TEXT]
STATEMENT: >>>
**コンポーネント収束図 (機能 → 共通基盤)**

.. raw:: html

    <pre class="mermaid">
    flowchart TB
        subgraph FEAT["機能ドメイン (L2 要求)"]
            A["01 Auth"]
            D["02 Data Access"]
            T["03 DTC"]
        end
        subgraph PLAT["共通プラットフォーム (L3 共有ユニット)"]
            TLS["TlsTerminator<br/>PLAT-L3-003"]
            SCOPE["ScopeAuthorizer<br/>PLAT-L3-002"]
            UDS["UdsClient<br/>PLAT-L3-001"]
            JSON["JsonSerializer<br/>PLAT-L3-004"]
        end
        A --> TLS
        A --> SCOPE
        D --> SCOPE
        D --> UDS
        D --> JSON
        T --> UDS
        T --> JSON
    </pre>

注: TlsTerminator は全機能ドメインの外部通信を終端するが、 TLS 要求は代表として
02-auth (AUTH-L1-005 / AUTH-L2-004) に集約されるため、 図では Auth からの依存のみを
示す。 なお 05-sw-update は独自の更新系ユニット群を持つため、 共通基盤への収束は
図に現れない。
<<<

[[SECTION]]
TITLE: 共通プラットフォーム ユニット (Shared Platform Units)

[REQUIREMENT]
UID: PLAT-L3-001
TYPE: Functional
ASIL: QM
LAYER: L3_Unit
TITLE: UdsClient ユニット (共有 UDS トランスポート)
STATEMENT: >>>
UdsClient ユニットは、 ISO 14229-1 準拠の UDS フレーム送受信を担い、 タイムアウト・
リトライ・NRC ハンドリングを提供すること。
<<<
RATIONALE: >>>
ゲートウェイ内の共有 UDS トランスポート。 データアクセスの ReadDataByIdentifier
ブリッジ (DATA-L2-002) と、 DTC の 0x19 読出 (DTC-L2-001) ・0x14 クリア (DTC-L2-003)
の双方から再利用される。 1 つのユニットが複数ドメインの上位要求を実現する収束 (N→1)。
<<<
RELATIONS:
- TYPE: Parent
  VALUE: DATA-L2-002
- TYPE: Parent
  VALUE: DTC-L2-001
- TYPE: Parent
  VALUE: DTC-L2-003

[REQUIREMENT]
UID: PLAT-L3-002
TYPE: Functional
ASIL: QM
CAL: CAL3
LAYER: L3_Unit
TITLE: ScopeAuthorizer ユニット (共有 認可)
STATEMENT: >>>
ScopeAuthorizer ユニットは、 (required_scope, token_scopes) を入力に許可・拒否を返し、
拒否時は理由コード (insufficient_scope / expired 等) を返すこと。
<<<
RATIONALE: >>>
認証 (AUTH-L2-003) と車両データアクセス (DATA-L2-006) の双方でスコープ検証に
再利用される共有ユニット。 1 つの下位要求が複数ドメインの上位要求を実現する収束 (N→1)。
<<<
RELATIONS:
- TYPE: Parent
  VALUE: AUTH-L2-003
- TYPE: Parent
  VALUE: DATA-L2-006

[REQUIREMENT]
UID: PLAT-L3-003
TYPE: Functional
ASIL: QM
CAL: CAL3
LAYER: L3_Unit
TITLE: TlsTerminator ユニット (共有 TLS 終端)
STATEMENT: >>>
TlsTerminator ユニットは、 OpenSSL ベースの TLS 終端を提供し、 起動時に信頼ストアを
ロードすること。
<<<
RATIONALE: >>>
全機能ドメインの外部通信を終端する横断的なセキュリティ基盤。 明示的な TLS 要求は
02-auth (AUTH-L1-005 / AUTH-L2-004) にあり、 本ユニットがそれを実装する。
<<<
VERIFICATION: >>>
ハンドシェイク失敗時に、 上位へエラーイベントが通知されること。
<<<
RELATIONS:
- TYPE: Parent
  VALUE: AUTH-L2-004

[REQUIREMENT]
UID: PLAT-L3-004
TYPE: Functional
ASIL: QM
LAYER: L3_Unit
TITLE: JsonSerializer ユニット (共有 応答エンコード)
STATEMENT: >>>
JsonSerializer ユニットは、 診断データ (DID 値: 整数・浮動小数・文字列・バイト列、
DTC 等) を ASAM SOVD JSON 形式に変換すること。
<<<
RATIONALE: >>>
SOVD の JSON 応答エンコードを担う共有ユニット。 データアクセス (DATA-L2-002) と
DTC (DTC-L2-001) の応答生成から再利用される。
<<<
RELATIONS:
- TYPE: Parent
  VALUE: DATA-L2-002
- TYPE: Parent
  VALUE: DTC-L2-001

[[/SECTION]]
