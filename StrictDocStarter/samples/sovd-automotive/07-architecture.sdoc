[DOCUMENT]
TITLE: SOVD アーキテクチャ 仕様 (System Architecture)

[GRAMMAR]
IMPORT_FROM_FILE: sovd-grammar.sgra

[TEXT]
STATEMENT: >>>
本書は、 SOVD 車両診断システムの **アーキテクチャ (設計 / HOW)** をシステム全体の視点で
定義する。 要求 (01-05、 WHAT) を実現する構造 — 方式・コンポーネント・モジュール・
ドメインモデル・振る舞い・設計判断 — をまとめる。

**設計の粒度ルール:** 各コンポーネントは **単一責務 (SRP) を 1 文** で表し、 責務を表す名前を
付ける。 インタフェース/構造は **クラス図** (3.4) で、 個々の **振る舞い (責務の仕様)** は
**テスト (08) のシナリオ** で表す (1 振る舞い = 1 シナリオ = 1 判定)。 各コンポーネントは
実現する要求へ ``Implements`` 関係でトレースする。

共有の前付けは `00-overview.sdoc`、 API 契約は `08-api.sdoc`、 テストは `09-test-spec.sdoc`。
<<<

[[SECTION]]
TITLE: 3.1 アーキテクチャ方式 (Architecture Concept)

[TEXT]
STATEMENT: >>>
**方式:** レイヤード + 基盤/機能の分離。 車両ゲートウェイ ECU が SOVD (HTTP/TLS) を
終端し、 内部は UDS にブリッジする (00-overview §3.1)。 機能ドメインは共通プラットフォーム
(05) の上に構築され、 依存方向は 機能 → 基盤 の一方向。 コンポーネント図・クラス図は
Clean Architecture (CA) レイヤーで色分けする。 凡例:

.. raw:: html

    <pre class="mermaid">
    graph RL
        subgraph Legend["CA Layer Legend (dependency direction)"]
            direction RL
            F["Framework"]:::framework -->|depends on| A["Adapter"]:::adapter
            A -->|depends on| U["Use Case"]:::usecase
            U -->|depends on| E["Entity"]:::entity
        end
        classDef entity fill:#FF8C00,stroke:#333,color:#000
        classDef usecase fill:#FFD700,stroke:#333,color:#000
        classDef adapter fill:#90EE90,stroke:#333,color:#000
        classDef framework fill:#87CEEB,stroke:#333,color:#000
    </pre>

Entity=橙 / Use Case=ゴールド / Adapter=緑 / Framework=青。
<<<

[[/SECTION]]

[[SECTION]]
TITLE: 3.2 コンポーネント (Components)

[TEXT]
STATEMENT: >>>
**代表スライス: 認証付き DID 読み出し (CA 層で色分け)**

.. raw:: html

    <pre class="mermaid">
    flowchart LR
        Client["SOVD Client"]:::framework
        TLS["TlsTerminator"]:::framework
        TV["TokenVerifier"]:::usecase
        SA["ScopeAuthorizer"]:::usecase
        DRU["DataReadUseCase"]:::usecase
        DID["DidResolver"]:::adapter
        UDS["UdsClient"]:::adapter
        JSON["JsonSerializer"]:::adapter
        ECU["Engine ECU"]:::framework
        Client --> TLS --> TV --> SA --> DRU
        DRU --> DID
        DRU --> UDS --> ECU
        DRU --> JSON
        classDef entity fill:#FF8C00,stroke:#333,color:#000
        classDef usecase fill:#FFD700,stroke:#333,color:#000
        classDef adapter fill:#90EE90,stroke:#333,color:#000
        classDef framework fill:#87CEEB,stroke:#333,color:#000
    </pre>

以下、 全ドメインの主要コンポーネントを **単一責務 (1 文)** で定義し、 要求へトレースする。
個々の振る舞い (受入/単体の判定) は 08 のシナリオを参照。
<<<

[TEXT]
STATEMENT: >>>
**基盤コンポーネント (Common Platform)**
<<<

[COMPONENT]
UID: ARCH-C-001
TITLE: TlsTerminator
CA_LAYER: Framework
STATEMENT: >>>
外部通信の TLS 1.3 を終端する。
<<<
MODULE: src/platform/tls_terminator.c
RELATIONS:
- TYPE: Parent
  VALUE: PLAT-L3-003
  ROLE: Implements

[COMPONENT]
UID: ARCH-C-002
TITLE: ScopeAuthorizer
CA_LAYER: UseCase
STATEMENT: >>>
要求スコープに基づき診断操作の認可可否を判定する。
<<<
MODULE: src/platform/scope_authorizer.c
RELATIONS:
- TYPE: Parent
  VALUE: PLAT-L3-002
  ROLE: Implements

[COMPONENT]
UID: ARCH-C-003
TITLE: UdsClient
CA_LAYER: Adapter
STATEMENT: >>>
車載 ECU と UDS フレームを送受信する (タイムアウト・リトライ・NRC を含む信頼性制御)。
<<<
MODULE: src/platform/uds_client.c
RELATIONS:
- TYPE: Parent
  VALUE: PLAT-L3-001
  ROLE: Implements

[COMPONENT]
UID: ARCH-C-004
TITLE: JsonSerializer
CA_LAYER: Adapter
STATEMENT: >>>
診断データを ASAM SOVD の JSON 形式へ変換する。
<<<
MODULE: src/platform/json_serializer.c
RELATIONS:
- TYPE: Parent
  VALUE: PLAT-L3-004
  ROLE: Implements

[TEXT]
STATEMENT: >>>
**認証ドメイン (02-auth)**
<<<

[COMPONENT]
UID: ARCH-C-005
TITLE: TokenVerifier
CA_LAYER: UseCase
STATEMENT: >>>
アクセストークン (JWT) の正当性 (署名・有効期限・claim) を検証する。
<<<
MODULE: src/auth/token_verifier.c
RELATIONS:
- TYPE: Parent
  VALUE: AUTH-L3-001
  ROLE: Implements

[COMPONENT]
UID: ARCH-C-006
TITLE: TokenCache
CA_LAYER: Adapter
STATEMENT: >>>
検証済みトークンを LRU でキャッシュする。
<<<
MODULE: src/auth/token_cache.c
RELATIONS:
- TYPE: Parent
  VALUE: AUTH-L3-002
  ROLE: Implements

[TEXT]
STATEMENT: >>>
**データアクセスドメイン (03-data-access)**
<<<

[COMPONENT]
UID: ARCH-C-007
TITLE: DataReadUseCase
CA_LAYER: UseCase
STATEMENT: >>>
DID 読出要求を統括し、 認可・解決・UDS 読出・JSON 変換の各基盤部品を協調させる。
<<<
MODULE: src/data/data_read_usecase.c
RELATIONS:
- TYPE: Parent
  VALUE: DATA-L2-002
  ROLE: Implements

[COMPONENT]
UID: ARCH-C-008
TITLE: DidResolver
CA_LAYER: Adapter
STATEMENT: >>>
DID 番号を担当 ECU のアドレスへ解決する。
<<<
MODULE: src/data/did_resolver.c
RELATIONS:
- TYPE: Parent
  VALUE: DATA-L3-001
  ROLE: Implements

[COMPONENT]
UID: ARCH-C-009
TITLE: DataCache
CA_LAYER: Adapter
STATEMENT: >>>
DID 値を TTL 付きでキャッシュする。
<<<
MODULE: src/data/data_cache.c
RELATIONS:
- TYPE: Parent
  VALUE: DATA-L3-002
  ROLE: Implements

[TEXT]
STATEMENT: >>>
**DTC ドメイン (04-dtc-diagnostics)**
<<<

[COMPONENT]
UID: ARCH-C-010
TITLE: DtcParser
CA_LAYER: Adapter
STATEMENT: >>>
UDS 0x19 のバイナリ応答を DTC リストへ解析する。
<<<
MODULE: src/dtc/dtc_parser.c
RELATIONS:
- TYPE: Parent
  VALUE: DTC-L3-001
  ROLE: Implements

[COMPONENT]
UID: ARCH-C-011
TITLE: FreezeFrameDecoder
CA_LAYER: Adapter
STATEMENT: >>>
フリーズフレームのペイロードを (DID, 値) のリストへ復号する。
<<<
MODULE: src/dtc/freeze_frame_decoder.c
RELATIONS:
- TYPE: Parent
  VALUE: DTC-L3-002
  ROLE: Implements

[COMPONENT]
UID: ARCH-C-012
TITLE: SpeedReader
CA_LAYER: Adapter
STATEMENT: >>>
車速を周期取得し、 最新値を提供する (ASIL C 認定タスク)。
<<<
MODULE: src/dtc/speed_reader.c
RELATIONS:
- TYPE: Parent
  VALUE: DTC-L3-003
  ROLE: Implements

[COMPONENT]
UID: ARCH-C-013
TITLE: DtcHistoryStore
CA_LAYER: Entity
STATEMENT: >>>
DTC 発生履歴をリングバッファで保持する。
<<<
MODULE: src/dtc/dtc_history_store.c
RELATIONS:
- TYPE: Parent
  VALUE: DTC-L3-004
  ROLE: Implements

[TEXT]
STATEMENT: >>>
**OTA ドメイン (05-sw-update)**
<<<

[COMPONENT]
UID: ARCH-C-014
TITLE: PackageDownloader
CA_LAYER: Adapter
STATEMENT: >>>
更新パッケージを再開可能な方式でダウンロードする。
<<<
MODULE: src/swupdate/package_downloader.c
RELATIONS:
- TYPE: Parent
  VALUE: SWU-L3-001
  ROLE: Implements

[COMPONENT]
UID: ARCH-C-015
TITLE: SignatureVerifier
CA_LAYER: UseCase
STATEMENT: >>>
更新パッケージの署名 (ECDSA P-256 / RSA-PSS 2048) を検証する。
<<<
MODULE: src/swupdate/signature_verifier.c
RELATIONS:
- TYPE: Parent
  VALUE: SWU-L3-002
  ROLE: Implements

[COMPONENT]
UID: ARCH-C-016
TITLE: FlashSectorWriter
CA_LAYER: Adapter
STATEMENT: >>>
フラッシュセクタを消去・書込し、 書込結果を CRC で検証する。
<<<
MODULE: src/swupdate/flash_sector_writer.c
RELATIONS:
- TYPE: Parent
  VALUE: SWU-L3-003
  ROLE: Implements

[COMPONENT]
UID: ARCH-C-017
TITLE: VehicleStateMonitor
CA_LAYER: Adapter
STATEMENT: >>>
フラッシュ書込の前提となる走行状態 (車速・PKB・シフト・IG) を判定する (ASIL D 認定)。
<<<
MODULE: src/swupdate/vehicle_state_monitor.c
RELATIONS:
- TYPE: Parent
  VALUE: SWU-L3-004
  ROLE: Implements

[[/SECTION]]

[[SECTION]]
TITLE: 3.3 モジュール / ファイル構成 (Module / File Structure)

[TEXT]
STATEMENT: >>>
.. code-block:: text

    src/
    |-- platform/                  # 06-common-platform (共有)
    |   |-- tls_terminator.c       # ARCH-C-001
    |   |-- scope_authorizer.c     # ARCH-C-002
    |   |-- uds_client.c           # ARCH-C-003
    |   `-- json_serializer.c      # ARCH-C-004
    |-- auth/                      # 02-auth
    |   |-- token_verifier.c       # ARCH-C-005
    |   `-- token_cache.c          # ARCH-C-006
    |-- data/                      # 03-data-access
    |   |-- data_read_usecase.c    # ARCH-C-007
    |   |-- did_resolver.c         # ARCH-C-008
    |   `-- data_cache.c           # ARCH-C-009
    |-- dtc/                       # 04-dtc-diagnostics
    |   |-- dtc_parser.c           # ARCH-C-010
    |   |-- freeze_frame_decoder.c # ARCH-C-011
    |   |-- speed_reader.c         # ARCH-C-012 (ASIL C)
    |   `-- dtc_history_store.c    # ARCH-C-013
    `-- swupdate/                  # 05-sw-update
        |-- package_downloader.c   # ARCH-C-014
        |-- signature_verifier.c   # ARCH-C-015
        |-- flash_sector_writer.c  # ARCH-C-016 (ASIL D)
        `-- vehicle_state_monitor.c# ARCH-C-017 (ASIL D)
<<<

[[/SECTION]]

[[SECTION]]
TITLE: 3.4 ドメインモデル (Domain Model)

[TEXT]
STATEMENT: >>>
**クラス図 1: 認証付き DID 読み出し** (各クラスのメソッド = コンポーネントのインタフェース)

.. raw:: html

    <pre class="mermaid">
    classDiagram
        class DataReadUseCase {
            +read(ecu, did) Json
        }
        class ScopeAuthorizer {
            +authorize(required, scopes) Decision
        }
        class TokenVerifier {
            +verify(jwt) VerifyResult
        }
        class DidResolver {
            +resolve(did) EcuAddress
        }
        class UdsClient {
            +readDataByIdentifier(addr, did) Bytes
        }
        class JsonSerializer {
            +serialize(value) Json
        }
        DataReadUseCase --> ScopeAuthorizer : uses
        DataReadUseCase --> DidResolver : uses
        DataReadUseCase --> UdsClient : uses
        DataReadUseCase --> JsonSerializer : uses
        ScopeAuthorizer ..> TokenVerifier : reads claims
    </pre>
<<<

[TEXT]
STATEMENT: >>>
**クラス図 2: DTC 読み出し / クリア**

.. raw:: html

    <pre class="mermaid">
    classDiagram
        class DtcParser {
            +parse(bytes) DtcList
        }
        class FreezeFrameDecoder {
            +decode(bytes) DidValueList
        }
        class SpeedReader {
            +currentSpeed() KmH
        }
        class DtcHistoryStore {
            +push(entry)
            +read(range) Entries
        }
        class UdsClient {
            +send(frame) Response
        }
        DtcParser --> UdsClient : via
        FreezeFrameDecoder --> UdsClient : via
    </pre>
<<<

[TEXT]
STATEMENT: >>>
**クラス図 3: OTA 更新**

.. raw:: html

    <pre class="mermaid">
    classDiagram
        class PackageDownloader {
            +download(url, range) Bytes
        }
        class SignatureVerifier {
            +verify(data, sig) bool
        }
        class FlashSectorWriter {
            +erase(sector)
            +write(sector, data) Status
        }
        class VehicleStateMonitor {
            +isFlashAllowed() bool
        }
        PackageDownloader ..> SignatureVerifier : package -> verify
        SignatureVerifier ..> FlashSectorWriter : if valid -> write
        FlashSectorWriter ..> VehicleStateMonitor : guarded by
    </pre>
<<<

[[/SECTION]]

[[SECTION]]
TITLE: 3.5 振る舞い (Behavior)

[TEXT]
STATEMENT: >>>
**システムシーケンス (代表スライス: 認証付き DID 読み出し、 端から端まで)**

.. raw:: html

    <pre class="mermaid">
    sequenceDiagram
        participant C as SOVD Client
        participant TCU as TCU
        participant TLS as TlsTerminator
        participant SA as ScopeAuthorizer
        participant DRU as DataReadUseCase
        participant UDS as UdsClient
        participant E as Engine ECU
        participant J as JsonSerializer
        C->>TCU: GET /components/engine/data/rpm (Bearer JWT)
        TCU->>TLS: forward over cellular
        TLS->>SA: verify scope read:did
        SA->>DRU: authorized
        DRU->>UDS: ReadDataByIdentifier(0xF40C)
        UDS->>E: UDS 0x22 F40C
        E-->>UDS: 0x62 F40C 0338
        UDS-->>DRU: 824
        DRU->>J: serialize(rpm=824)
        J-->>C: 200 {"rpm": 824}
    </pre>

他ドメインの代表シーケンス (認証フロー・DTC ガード・OTA 状態機械) は各要求文書
(01/03/04) に置く。
<<<

[[/SECTION]]

[[SECTION]]
TITLE: 3.6 設計判断 (Architecture Decision Records)

[TEXT]
STATEMENT: >>>
**ADR-001: SOVD をゲートウェイで終端し UDS にブリッジ**

- Status: Accepted
- Context: 車外は HTTP/REST (SOVD)、 車内は既存の UDS (ISO 14229)。
- Decision: ゲートウェイ ECU で SOVD を終端し、 内部 ECU へ UDS で中継する。
- Consequences: 既存 ECU を変えずに SOVD 化できる。 ゲートウェイに変換層が集中する。
<<<

[TEXT]
STATEMENT: >>>
**ADR-002: 基盤 / 機能の分離 (共通プラットフォーム)**

- Status: Accepted
- Context: UDS 転送・認可・TLS・JSON は複数機能が使う。
- Decision: 共有コンポーネントを 06-common-platform に括り出し、 機能はそこへ依存する。
- Consequences: 依存方向が 機能 → 基盤 に一本化。 兄弟機能間の結合を排除。 収束 (N→1)
  がトレースに現れる。
<<<

[TEXT]
STATEMENT: >>>
**ADR-003: 安全 (ASIL) とセキュリティ (CAL) を分離**

- Status: Accepted
- Context: 認証等のセキュリティ要求に ASIL を付けると安全/セキュリティが混線する。
- Decision: ASIL=ISO 26262 (安全)、 CAL=ISO/SAE 21434 (セキュリティ) を別フィールドで管理。
- Consequences: 純セキュリティ要求は ASIL=QM+CAL、 安全関連は ASIL、 両者交差は両方を持つ。
<<<

[TEXT]
STATEMENT: >>>
**ADR-004: OTA は A/B パーティション + 状態機械**

- Status: Accepted
- Context: 走行中書込・改ざん・書込失敗のリスク。
- Decision: 非アクティブ側へ書込み、 署名検証成功時のみ切替、 失敗時は旧版維持。 状態機械
  (04 §L1) で未検証適用を構造的に禁止。
- Consequences: ロールバック容易。 安全関連 ECU の更新時保護を要求レベルで担保 (ASIL D)。
<<<

[TEXT]
STATEMENT: >>>
**ADR-005: コンポーネントは単一責務 (SRP)、 振る舞いはテストで仕様化**

- Status: Accepted
- Context: 責務と仕様 (振る舞い) を 1 ノードに混載すると、 個別の検証・合否が追えない。
- Decision: コンポーネントは単一責務 (1 文) + 責務ベースの命名に限定し、 個々の振る舞いは
  テスト (08) のシナリオで表す (1 振る舞い = 1 シナリオ = 1 判定)。
- Consequences: 各振る舞いが独立して合否を持ち、 マトリクスで未達まで追える。 命名から実装
  詳細 (Table/Buffer 等) を排除。
<<<

[[/SECTION]]
