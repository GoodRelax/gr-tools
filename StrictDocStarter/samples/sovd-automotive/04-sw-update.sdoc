[DOCUMENT]
TITLE: SOVD ソフトウェア更新 (OTA) 要求仕様 (Software Update)

[GRAMMAR]
IMPORT_FROM_FILE: sovd-grammar.sgra

[TEXT]
STATEMENT: >>>
本書は SOVD 経由の **OTA (Over-The-Air) ソフトウェア更新** の要求を L0→L3 で定義する。
ダウンロード・署名検証・インストール・ロールバックの 4 フェーズと、 機能安全
(ISO 26262) 関連 ECU の更新時保護を含む。 共有の前付けは `00-overview.sdoc`、
認証・認可は `01-auth.sdoc` を前提とする。

本書は **安全 (ASIL) とセキュリティ (CAL) が交差する** ドメインである:
走行中のフラッシュ書込禁止は **安全 (ASIL D)**、 署名検証は **改ざん FW の適用阻止**
であり安全とセキュリティの両面を持つため **ASIL D かつ CAL4** を付与する (00-overview §6.3)。
<<<

[[SECTION]]
TITLE: L0 — ステークホルダ要求 (Stakeholder Requirements)

[TEXT]
STATEMENT: >>>
**ストーリー:** 車の不具合の多くは、 部品交換ではなくソフトウェアの更新で直せる。
昔はそのために車を工場へ入れ、 有線でリプログラミングする必要があった。 OTA では、
OEM が不具合修正ソフトを **無線で遠隔配信** し、 工場に入れずに更新できる。 ただし
ソフト更新は安全関連 ECU を書き換えうるため、 **走行中は書き換えない・署名を検証する・
失敗したら元のバージョンに戻す** という安全策を要求レベルで規定する。
<<<

[REQUIREMENT]
UID: SWU-L0-001
TYPE: UseCase
ASIL: QM
CAL: CAL3
LAYER: L0_Stakeholder
TITLE: OTA による遠隔ソフトウェア更新
STATEMENT: >>>
OEM が不具合修正ソフトを配信したいとき、 本システムは車両 ECU のソフトウェアを OTA
(無線) で更新できるようにし、 ドライバーが進捗を SOVD クライアントで確認できるように
すること。
<<<
VERIFICATION: >>>
署名付きパッケージの配信 → 適用 → 進捗確認が一連で行え、 適用後に新バージョンで
起動すること。
<<<

[REQUIREMENT]
UID: SWU-L0-002
TYPE: Functional
ASIL: D
CAL: CAL4
LAYER: L0_Stakeholder
TITLE: 改ざん検知 (署名検証)
STATEMENT: >>>
本システムは、 更新パッケージのデジタル署名を検証して改ざん・偽造を検知すること。
もし署名検証に失敗した場合、 当該パッケージをインストールしないこと。
<<<
RATIONALE: >>>
不正なファームウェアの注入は安全関連 ECU の機能喪失に直結し (安全)、 かつ車両は
攻撃対象となる (セキュリティ)。 そのため安全・セキュリティの双方で最高保証レベルとする。
<<<
RELATIONS:
- TYPE: Parent
  VALUE: SWU-L0-001

[REQUIREMENT]
UID: SWU-L0-003
TYPE: Functional
ASIL: C
LAYER: L0_Stakeholder
TITLE: ロールバック対応
STATEMENT: >>>
もし更新後に異常が検出された場合、 本システムは直前のバージョンへ自動または手動で
ロールバックできること。
<<<
RELATIONS:
- TYPE: Parent
  VALUE: SWU-L0-001

[REQUIREMENT]
UID: SWU-L0-004
TYPE: Restriction
ASIL: D
LAYER: L0_Stakeholder
TITLE: 走行中の更新禁止
STATEMENT: >>>
もし車両が IG-ON かつ車速 > 0 の場合、 本システムは ECU フラッシュ書込を開始しない
こと。 ダウンロードのみ走行中も許容する。
<<<
RATIONALE: >>>
走行中の書込中断や挙動変化は、 安全機能の喪失に直結するため。
<<<
RELATIONS:
- TYPE: Parent
  VALUE: SWU-L0-001

[REQUIREMENT]
UID: SWU-L0-005
TYPE: Non-Functional
ASIL: QM
LAYER: L0_Stakeholder
TITLE: 更新所要時間
STATEMENT: >>>
本システムの 1 ECU 当たりの平均更新時間 (検証 + 書込 + 再起動) は、 5 分以内で
あること。
<<<
RELATIONS:
- TYPE: Parent
  VALUE: SWU-L0-001

[[/SECTION]]

[[SECTION]]
TITLE: L1 — システム要求 (System Requirements)

[TEXT]
STATEMENT: >>>
**L1 の状態機械: OTA 更新フェーズ**

OTA 更新は次の状態機械に従う。 署名検証 (Verifying) に失敗したら Installing へ
遷移せず Failed とし、 書込 (Installing) に失敗したら RolledBack で旧バージョンへ戻す。
これにより「未検証パッケージの適用」 を構造的に禁止する (SWU-L1-008)。

.. raw:: html

    <pre class="mermaid">
    stateDiagram-v2
        [*] --> Idle
        Idle --> Downloading: POST /updates
        Downloading --> Verifying: package received
        Verifying --> Installing: signature valid
        Verifying --> Failed: signature invalid
        Installing --> Activated: flash OK
        Installing --> RolledBack: flash error
        Activated --> [*]
        RolledBack --> Idle
        Failed --> Idle
    </pre>
<<<

[REQUIREMENT]
UID: SWU-L1-001
TYPE: Functional
ASIL: QM
CAL: CAL3
LAYER: L1_System
TITLE: 更新パッケージのダウンロード
STATEMENT: >>>
車両は POST /updates エンドポイントを提供し、 OEM サーバから更新パッケージ
(バイナリ + マニフェスト + 署名) を取得すること。
<<<
RELATIONS:
- TYPE: Parent
  VALUE: SWU-L0-001

[REQUIREMENT]
UID: SWU-L1-002
TYPE: Functional
ASIL: D
CAL: CAL4
LAYER: L1_System
TITLE: パッケージ署名検証
STATEMENT: >>>
パッケージをダウンロードしたとき、 車両は OEM ルート証明書チェーンで RSA-PSS
2048-bit 以上の署名を検証し、 もし失敗した場合はパッケージを破棄すること。
<<<
VERIFICATION: >>>
改ざんされたパッケージが破棄され、 インストールに進まないこと。
<<<
RELATIONS:
- TYPE: Parent
  VALUE: SWU-L0-002

[REQUIREMENT]
UID: SWU-L1-003
TYPE: Functional
ASIL: D
LAYER: L1_System
TITLE: A/B パーティション切替
STATEMENT: >>>
車両の ECU は A/B パーティション構成を持ち、 新ファームウェアを非アクティブ
パーティションに書込み、 ブートローダ経由で切替えること。 もし切替に失敗した場合は
前パーティションを維持すること。
<<<
RELATIONS:
- TYPE: Parent
  VALUE: SWU-L0-003

[REQUIREMENT]
UID: SWU-L1-004
TYPE: Functional
ASIL: D
LAYER: L1_System
TITLE: 走行状態ガード
STATEMENT: >>>
フラッシュ書込を開始する前に、 車両は次の全条件を満たすことを確認すること:
(a) 車速 == 0、 (b) パーキングブレーキ ON、 (c) シフト P、 (d) IG-OFF または ACC 状態。
<<<
VERIFICATION: >>>
4 条件のいずれかが崩れている状態で、 フラッシュ書込が開始されないこと。
<<<
RELATIONS:
- TYPE: Parent
  VALUE: SWU-L0-004

[REQUIREMENT]
UID: SWU-L1-005
TYPE: Functional
ASIL: C
LAYER: L1_System
TITLE: ロールバック API
STATEMENT: >>>
車両は POST /updates/rollback で前バージョンへの即時ロールバックを実行できるように
すること。 ロールバック中は車両機能を制限すること。
<<<
RELATIONS:
- TYPE: Parent
  VALUE: SWU-L0-003

[REQUIREMENT]
UID: SWU-L1-006
TYPE: Functional
ASIL: QM
LAYER: L1_System
TITLE: 更新進捗ストリーム
STATEMENT: >>>
車両は GET /updates/progress (Server-Sent Events) で、 各 ECU の更新進捗 (0..100%) と
現フェーズを SOVD クライアントへプッシュ通知すること。
<<<
RELATIONS:
- TYPE: Parent
  VALUE: SWU-L0-001

[REQUIREMENT]
UID: SWU-L1-007
TYPE: Functional
ASIL: QM
LAYER: L1_System
TITLE: 中断耐性
STATEMENT: >>>
もし更新中に電源断・通信切断が発生した場合、 再開時に車両は、 ダウンロード中であれば
再開、 書込中であれば最初からリトライ、 完了済であればスキップとすること。
<<<
RELATIONS:
- TYPE: Parent
  VALUE: SWU-L0-003

[REQUIREMENT]
UID: SWU-L1-008
TYPE: Functional
ASIL: D
CAL: CAL4
LAYER: L1_System
TITLE: OTA 状態機械の遵守
STATEMENT: >>>
車両の OTA 更新は上図の状態機械に従うこと。 署名検証 (Verifying) に失敗した場合は
Installing に遷移せず Failed とし、 フラッシュ失敗時は RolledBack で旧版に戻すこと。
<<<
RATIONALE: >>>
署名検証に失敗したパッケージの適用を、 状態遷移によって構造的に禁止する。 同じ状態機械が
フラッシュ失敗時の RolledBack 遷移によりロールバック (SWU-L0-003) も実現するため、
1 つの要求で 2 つの上位要求 (改ざん検知・ロールバック) を満たす収束 (N→1) の例。
<<<
RELATIONS:
- TYPE: Parent
  VALUE: SWU-L0-002
- TYPE: Parent
  VALUE: SWU-L0-003

[[/SECTION]]

[[SECTION]]
TITLE: L2 — ECU ソフトウェア要求 (ECU Software Requirements)

[REQUIREMENT]
UID: SWU-L2-001
TYPE: Functional
ASIL: QM
CAL: CAL3
LAYER: L2_ECU_SW
TITLE: ダウンロードマネージャ
STATEMENT: >>>
ゲートウェイ ECU は DownloadManager を実装し、 HTTPS Range リクエストによる分割
ダウンロード・進捗報告・整合性チェック (SHA-256) を行うこと。
<<<
RELATIONS:
- TYPE: Parent
  VALUE: SWU-L1-001

[REQUIREMENT]
UID: SWU-L2-002
TYPE: Functional
ASIL: D
CAL: CAL4
LAYER: L2_ECU_SW
TITLE: 署名検証エンジン
STATEMENT: >>>
SignatureVerifier は ECDSA P-256 と RSA-PSS 2048 の両方をサポートし、 OEM ルート CA で
署名チェーンを検証すること。
<<<
RELATIONS:
- TYPE: Parent
  VALUE: SWU-L1-002

[REQUIREMENT]
UID: SWU-L2-003
TYPE: Functional
ASIL: D
LAYER: L2_ECU_SW
TITLE: フラッシュ書込ドライバ
STATEMENT: >>>
FlashWriter は ECU 内 NOR フラッシュへの書込を担い、 書込後に CRC32 ベリファイを
必須とすること。
<<<
RELATIONS:
- TYPE: Parent
  VALUE: SWU-L1-003

[REQUIREMENT]
UID: SWU-L2-004
TYPE: Functional
ASIL: D
LAYER: L2_ECU_SW
TITLE: VehicleStateGuard
STATEMENT: >>>
VehicleStateGuard は更新開始前に SWU-L1-004 の 4 条件を 50 ms 周期で監視し、 もし
1 つでも崩れた場合は書込を緊急中断すること。
<<<
RELATIONS:
- TYPE: Parent
  VALUE: SWU-L1-004

[REQUIREMENT]
UID: SWU-L2-005
TYPE: Functional
ASIL: C
LAYER: L2_ECU_SW
TITLE: ロールバックマネージャ
STATEMENT: >>>
RollbackManager は前バージョンのパーティション情報を保持し、 ロールバック要求時に
ブートローダパラメータを書き換えて再起動を要求すること。
<<<
RELATIONS:
- TYPE: Parent
  VALUE: SWU-L1-005

[REQUIREMENT]
UID: SWU-L2-006
TYPE: Functional
ASIL: QM
LAYER: L2_ECU_SW
TITLE: 進捗イベントバス
STATEMENT: >>>
各更新フェーズ (download / verify / write / finalize) は ProgressEventBus にイベントを
publish し、 SSE エンドポイントが subscribe して配信すること。
<<<
RELATIONS:
- TYPE: Parent
  VALUE: SWU-L1-006

[REQUIREMENT]
UID: SWU-L2-007
TYPE: Functional
ASIL: QM
LAYER: L2_ECU_SW
TITLE: 再開可能ステートマシン
STATEMENT: >>>
更新ステートマシンの状態は不揮発領域に保存され、 電源断後の再起動で最後の安全状態から
再開できること。
<<<
RELATIONS:
- TYPE: Parent
  VALUE: SWU-L1-007

[REQUIREMENT]
UID: SWU-L2-008
TYPE: Constraint
ASIL: D
LAYER: L2_ECU_SW
TITLE: ASIL D 開発プロセス
STATEMENT: >>>
SignatureVerifier / FlashWriter / VehicleStateGuard は ISO 26262 ASIL D 準拠の開発
プロセスで構築し、 ユニットテストカバレッジ 100% を達成すること。
<<<
RELATIONS:
- TYPE: Parent
  VALUE: SWU-L1-002

[[/SECTION]]

[[SECTION]]
TITLE: L3 — ユニット要求 (Unit / Software Component Requirements)

[REQUIREMENT]
UID: SWU-L3-001
TYPE: Functional
ASIL: QM
CAL: CAL3
LAYER: L3_Unit
TITLE: PackageDownloader ユニット
STATEMENT: >>>
PackageDownloader ユニットは、 1 MB チャンク単位の HTTPS Range ダウンロードを実装し、
失敗時のリトライ (指数バックオフ 1s..30s) を提供すること。
<<<
RELATIONS:
- TYPE: Parent
  VALUE: SWU-L2-001

[REQUIREMENT]
UID: SWU-L3-002
TYPE: Functional
ASIL: D
CAL: CAL4
LAYER: L3_Unit
TITLE: SignatureVerifier ユニット
STATEMENT: >>>
SignatureVerifier ユニットは、 OpenSSL を用いて ECDSA P-256 および RSA-PSS 2048 の
署名を検証する、 内部状態を持たない純粋関数として実装すること。
<<<
RELATIONS:
- TYPE: Parent
  VALUE: SWU-L2-002

[REQUIREMENT]
UID: SWU-L3-003
TYPE: Functional
ASIL: D
LAYER: L3_Unit
TITLE: FlashSectorWriter ユニット
STATEMENT: >>>
FlashSectorWriter ユニットは、 64 KB セクタの消去・書込・CRC32 計算を提供し、 write 操作は
事前のセクタ消去を必須とし、 もし失敗した場合は ERROR_FLASH_VERIFY を返すこと。
<<<
RELATIONS:
- TYPE: Parent
  VALUE: SWU-L2-003

[REQUIREMENT]
UID: SWU-L3-004
TYPE: Functional
ASIL: D
LAYER: L3_Unit
TITLE: VehicleStateMonitor ユニット
STATEMENT: >>>
VehicleStateMonitor ユニットは、 車速・パーキングブレーキ・シフト・IG 信号を CAN から
読み出し、 全条件を満たす場合のみ TRUE を返すこと (ASIL D 認定)。
<<<
RELATIONS:
- TYPE: Parent
  VALUE: SWU-L2-004

[REQUIREMENT]
UID: SWU-L3-005
TYPE: Constraint
ASIL: D
LAYER: L3_Unit
TITLE: 開発言語制限
STATEMENT: >>>
ASIL D 認定ユニットは、 MISRA C:2012 準拠の C 言語のみで実装し、 動的メモリ確保禁止・
再帰呼出禁止・全関数の循環的複雑度 <= 10 とすること。
<<<
RELATIONS:
- TYPE: Parent
  VALUE: SWU-L2-008

[[/SECTION]]
