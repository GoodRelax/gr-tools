[DOCUMENT]
TITLE: SOVD 故障診断 (DTC) 要求仕様 (Diagnostic Trouble Codes)

[GRAMMAR]
IMPORT_FROM_FILE: sovd-grammar.sgra

[TEXT]
STATEMENT: >>>
本書は SOVD の **故障診断 (DTC・フリーズフレーム)** の読出・クリア要求を L1→L3 で
定義する。 内部では ISO 14229 (UDS) の 0x19 系 (ReadDTCInformation) / 0x14
(ClearDiagnosticInformation) を SOVD でラップする。 ステークホルダ要求 (L0)・ユースケースは
`01-stakeholder-requirements.sdoc`、 共有の前付けは `00-overview.sdoc`、 認証・認可は
`03-auth.sdoc` を前提とする。

DTC の **読み出し** は安全機能ではないため原則 **ASIL=QM**。 ただし **「走行中に
安全関連 DTC を消す」 と機能安全評価に影響しうる** ため、 クリアの **走行状態ガードは
ASIL C** とする。 「誰がクリアできるか」 の権限はセキュリティ事項なので **CAL** を付与する。
<<<

[[SECTION]]
TITLE: L1 — システム要求 (System Requirements)

[TEXT]
STATEMENT: >>>
**L1 代表シーケンス: DTC の読み出しと、 走行状態ガード付きクリア**

読み出しは UDS 0x19 へ、 クリアは UDS 0x14 へブリッジする。 クリアは車速ゼロを
確認できた場合のみ実行し、 走行中は 409 で拒否する。

.. raw:: html

    <pre class="mermaid">
    sequenceDiagram
        participant C as SOVD Client
        participant G as Gateway ECU
        participant E as ECU
        C->>G: GET /components/engine/faults (Bearer JWT)
        G->>E: UDS 0x19 02 (reportDTCByStatusMask)
        E-->>G: DTC list + status
        G-->>C: 200 OK [{code, status}]
        C->>G: DELETE /components/engine/faults (scope write:dtc)
        G->>G: read vehicle speed (DID 0xF40D)
        alt vehicle stopped (speed == 0)
            G->>E: UDS 0x14 (ClearDiagnosticInformation)
            G-->>C: 204 No Content
        else vehicle moving (speed > 0)
            G-->>C: 409 Conflict
        end
    </pre>
<<<

[REQUIREMENT]
UID: DTC-L1-001
TYPE: Functional
ASIL: QM
LAYER: L1_System
TITLE: DTC リスト取得 API
STATEMENT: >>>
車両は GET /components/{ecu}/faults を提供し、 ステータスマスク
(active/pending/confirmed/permanent) でフィルタ可能とすること。
<<<
RELATIONS:
- TYPE: Parent
  VALUE: DTC-L0-001

[REQUIREMENT]
UID: DTC-L1-002
TYPE: Functional
ASIL: QM
LAYER: L1_System
TITLE: フリーズフレーム取得 API
STATEMENT: >>>
車両は GET /components/{ecu}/faults/{code}/freeze-frame で、 指定 DTC のフリーズフレーム
(発生時の DID 値スナップショット) を JSON で返すこと。
<<<
RELATIONS:
- TYPE: Parent
  VALUE: DTC-L0-002

[REQUIREMENT]
UID: DTC-L1-003
TYPE: Functional
ASIL: QM
CAL: CAL2
LAYER: L1_System
TITLE: DTC クリア API
STATEMENT: >>>
車両は DELETE /components/{ecu}/faults/{code} で DTC をクリアできるようにし、
スコープ write:dtc を要求すること。
<<<
RELATIONS:
- TYPE: Parent
  VALUE: DTC-L0-003

[REQUIREMENT]
UID: DTC-L1-004
TYPE: Functional
ASIL: C
LAYER: L1_System
TITLE: クリア前の車速ゼロチェック
STATEMENT: >>>
DTC クリア要求を受信したとき、 車両は現在の車速 (DID 0xF40D) を読み出し、 もし 0 km/h でなければ HTTP 409 Conflict を返すこと。 車速を取得できない場合も、 安全側に倒してクリアを実行せず拒否すること。
<<<
VERIFICATION: >>>
車速 > 0 でのクリア要求が 409 で拒否され、 車速 0 でのみ成功すること。
<<<
RELATIONS:
- TYPE: Parent
  VALUE: DTC-L0-004

[REQUIREMENT]
UID: DTC-L1-005
TYPE: Functional
ASIL: QM
CAL: CAL2
LAYER: L1_System
TITLE: 全 DTC 一括クリア API
STATEMENT: >>>
車両は DELETE /components/{ecu}/faults で全 DTC を一括クリアできるようにすること
(車速ゼロ条件は DTC-L1-004 と同じ)。
<<<
RELATIONS:
- TYPE: Parent
  VALUE: DTC-L0-003
- TYPE: Parent
  VALUE: DTC-L0-004

[REQUIREMENT]
UID: DTC-L1-006
TYPE: Non-Functional
ASIL: QM
LAYER: L1_System
TITLE: DTC レスポンス時間
STATEMENT: >>>
車両の DTC リスト取得は、 95 パーセンタイルで 1 秒以内に応答すること。
<<<
VERIFICATION: >>>
代表負荷下で、 DTC リスト取得の p95 が 1 秒以内であること。
<<<
RELATIONS:
- TYPE: Parent
  VALUE: DTC-L1-001

[REQUIREMENT]
UID: DTC-L1-007
TYPE: Functional
ASIL: QM
LAYER: L1_System
TITLE: DTC 発生履歴
STATEMENT: >>>
車両は、 直近 1024 件 (概ね 24 時間相当) の DTC 発生履歴を保持し、 GET
/components/{ecu}/faults/history で取得できるようにすること。
<<<
RELATIONS:
- TYPE: Parent
  VALUE: DTC-L0-001

[REQUIREMENT]
UID: DTC-L1-008
TYPE: Functional
ASIL: QM
CAL: CAL2
LAYER: L1_System
TITLE: 安全関連 DTC クリアの権限検証
STATEMENT: >>>
もし安全関連 DTC のクリアが要求された場合、 車両は write:dtc:safety スコープを
検証し、 欠く場合は HTTP 403 を返すこと。
<<<
VERIFICATION: >>>
安全関連 DTC のクリアが、 write:dtc のみのトークンで 403、 write:dtc:safety を
伴う場合に許可されること。
<<<
RELATIONS:
- TYPE: Parent
  VALUE: DTC-L0-006

[[/SECTION]]

[[SECTION]]
TITLE: L2 — ECU ソフトウェア要求 (ECU Software Requirements)

[REQUIREMENT]
UID: DTC-L2-001
TYPE: Functional
ASIL: QM
LAYER: L2_ECU_SW
TITLE: UDS 0x19 ReadDTCInformation ブリッジ
STATEMENT: >>>
SOVD GET /faults 要求を受けたとき、 ゲートウェイ ECU は担当 ECU 群へ UDS Service
0x19 SubFunction 0x02 (reportDTCByStatusMask) を発行し、 結果を集約して JSON で
返すこと。
<<<
RELATIONS:
- TYPE: Parent
  VALUE: DTC-L1-001

[REQUIREMENT]
UID: DTC-L2-002
TYPE: Functional
ASIL: QM
LAYER: L2_ECU_SW
TITLE: フリーズフレーム取得
STATEMENT: >>>
ゲートウェイ ECU は、 UDS 0x19 SubFunction 0x04
(reportDTCSnapshotRecordByDTCNumber) を用いてフリーズフレームを取得すること。
<<<
RELATIONS:
- TYPE: Parent
  VALUE: DTC-L1-002

[REQUIREMENT]
UID: DTC-L2-003
TYPE: Functional
ASIL: QM
CAL: CAL2
LAYER: L2_ECU_SW
TITLE: UDS 0x14 ClearDiagnosticInformation
STATEMENT: >>>
DTC クリア要求に対し、 ゲートウェイ ECU は車速チェック (DTC-L2-004) の成功後に
UDS Service 0x14 を対象 ECU へ発行すること。
<<<
RELATIONS:
- TYPE: Parent
  VALUE: DTC-L1-003

[REQUIREMENT]
UID: DTC-L2-004
TYPE: Functional
ASIL: C
LAYER: L2_ECU_SW
TITLE: VehicleSpeedGuard
STATEMENT: >>>
全ての DTC クリア要求 (個別・一括を問わず) の前に、 ゲートウェイ ECU は VehicleSpeedGuard により車速 == 0 を
100 ms 以内に検証すること。
<<<
VERIFICATION: >>>
車速 > 0 のときクリアが実行されないこと (ガードで阻止) を確認する。
<<<
RELATIONS:
- TYPE: Parent
  VALUE: DTC-L1-004

[REQUIREMENT]
UID: DTC-L2-005
TYPE: Functional
ASIL: QM
LAYER: L2_ECU_SW
TITLE: DTC マスタテーブル
STATEMENT: >>>
ゲートウェイ ECU は、 OEM 提供の DTC マスタテーブル (コード → 説明 / 推奨対処) を
NVRAM に保持し、 API レスポンスに同梱すること。
<<<
RELATIONS:
- TYPE: Parent
  VALUE: DTC-L1-001

[REQUIREMENT]
UID: DTC-L2-006
TYPE: Functional
ASIL: QM
LAYER: L2_ECU_SW
TITLE: DTC 履歴循環バッファ
STATEMENT: >>>
ゲートウェイ ECU は、 最大 1024 件の DTC 履歴を循環バッファで保持すること
(タイムスタンプ + DTC + status mask を 1 エントリとする)。
<<<
RELATIONS:
- TYPE: Parent
  VALUE: DTC-L1-007

[REQUIREMENT]
UID: DTC-L2-007
TYPE: Non-Functional
ASIL: QM
LAYER: L2_ECU_SW
TITLE: UDS タイムアウト
STATEMENT: >>>
ゲートウェイ ECU の UDS 要求の P2 タイムアウトは 50 ms、 P2* タイムアウトは
500 ms とすること。
<<<
RELATIONS:
- TYPE: Parent
  VALUE: DTC-L1-006

[REQUIREMENT]
UID: DTC-L2-008
TYPE: Constraint
ASIL: QM
LAYER: L2_ECU_SW
TITLE: NRC ハンドリング
STATEMENT: >>>
もし UDS Negative Response Code (NRC) を受けた場合、 ゲートウェイ ECU は SOVD
クライアントへ HTTP 502 と、 JSON ボディに NRC コードを含めて返すこと。
<<<
RELATIONS:
- TYPE: Parent
  VALUE: DTC-L2-001

[[/SECTION]]

[[SECTION]]
TITLE: L3 — ユニット要求 (Unit / Software Component Requirements)

[REQUIREMENT]
UID: DTC-L3-001
TYPE: Functional
ASIL: QM
LAYER: L3_Unit
TITLE: DtcParser ユニット
STATEMENT: >>>
DtcParser ユニットは、 UDS 0x19 のバイナリ応答を解析し、 (dtc_code, status_byte) の
リストを返すこと。
<<<
RELATIONS:
- TYPE: Parent
  VALUE: DTC-L2-001

[REQUIREMENT]
UID: DTC-L3-002
TYPE: Functional
ASIL: QM
LAYER: L3_Unit
TITLE: FreezeFrameDecoder ユニット
STATEMENT: >>>
FreezeFrameDecoder ユニットは、 UDS 0x19/0x04 のフリーズフレームペイロードを
(did, value) のリストに変換すること。
<<<
RELATIONS:
- TYPE: Parent
  VALUE: DTC-L2-002

[REQUIREMENT]
UID: DTC-L3-003
TYPE: Functional
ASIL: C
LAYER: L3_Unit
TITLE: SpeedReader ユニット
STATEMENT: >>>
SpeedReader ユニットは、 ASIL C 認定のリアルタイムタスクとして DID 0xF40D を 10 ms
周期で更新し、 最新値を const アクセスで提供すること。
<<<
RELATIONS:
- TYPE: Parent
  VALUE: DTC-L2-004

[REQUIREMENT]
UID: DTC-L3-004
TYPE: Functional
ASIL: QM
LAYER: L3_Unit
TITLE: DtcHistoryStore ユニット
STATEMENT: >>>
DtcHistoryStore ユニットは、 ロックフリーのリングバッファ (Single Producer Multiple
Consumer) として実装し、 サイズ 1024 を NVRAM 上に確保すること。
<<<
RELATIONS:
- TYPE: Parent
  VALUE: DTC-L2-006

[REQUIREMENT]
UID: DTC-L3-005
TYPE: Constraint
ASIL: QM
LAYER: L3_Unit
TITLE: NVRAM 摩耗保護
STATEMENT: >>>
DTC 履歴の NVRAM 書込は wear-leveling アルゴリズム (例: log-structured) を採用し、
同一セクタへの連続書込を避けること。
<<<
RELATIONS:
- TYPE: Parent
  VALUE: DTC-L3-004

[[/SECTION]]
